module holo-vrrp {
  yang-version 1.1;
  namespace "http://holo-routing.org/yang/holo-vrrp";
  prefix holo-vrrp;

  import ietf-routing {
    prefix rt;
  }

  organization
    "Holo Routing Stack";

  description
    "This module defines augment statements for the ietf-vrrp
     module.";

  /*
   * Identities.
   */

  identity vrrp {
    base rt:routing-protocol;
    description
      "VRRP protocol.";
  }

  identity vrrpv2 {
    base rt:routing-protocol;
    description
      "VRRP V2 protocol.";
  }

  identity vrrpv3 {
    base rt:routing-protocol;
    description
      "VRRP V3 protocol.";
  }
}
